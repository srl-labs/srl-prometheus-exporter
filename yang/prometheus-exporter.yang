module prometheus-exporter {
    yang-version "1.1";

    // namespace
    namespace "urn:srl_sdk_apps/prometheus-exporter";
    prefix "srl_sdk_apps-prometheus-exporter";

    import srl_nokia-common {
        prefix srl-comm;
    }
    import srl_nokia-system {
        prefix srl-system;
    }
    import srl_nokia-ndk {
        prefix srl-ndk;
    }
    import srl_nokia-grpc {
        prefix srl-grpc;
    }
    import srl_nokia-network-instance {
        prefix srl-netinst;
    }
    import srl_nokia-tls {
        prefix srl-tls;
    }
    import srl_nokia-extensions {
        prefix srl-ext;
    }

    // description
    description
        "This module defines configuration and operational state data related to the SRLinux Prometheus Exporter.";

    // revision(s)
    revision "2026-10-08" {
        description
          "prometheus-exporter 0.3.1. Remote write from a gNMI SAMPLE subscription.";
    }
    revision "2026-10-07" {
        description
          "prometheus-exporter 0.3.0. Breaking: SRL 26.7 metric paths and NDK v0.5 via srl-labs/bond.";
    }
    revision "2026-03-05" {
        description
          "prometheus-exporter 0.2.15";
    }
    revision "2020-10-15" {
        description
          "prometheus-exporter 0.1.0";
    }
    revision "2020-09-22" {
        description
          "prometheus-exporter 0.2.0";
    }
    grouping prometheus-exporter-top {
        container prometheus-exporter {
            //presence "prometheus-exporter";
            container scrape {
                description
                  "HTTP listener Prometheus scrapes. Disable admin-state to use remote-write only.";
                leaf admin-state {
                    type srl-comm:admin-state;
                    default "enable";
                    description "Administrative state of the scrape listener.";
                }
                leaf address {
                    type srl-comm:ip-address;
                    default "::";
                    srl-ext:show-importance high;
                    description
                      "IP address the scrape listener uses. The CPM filter must permit TCP to the port.";
                }
                leaf port {
                    type srl-comm:port-number;
                    default "8888";
                    srl-ext:show-importance high;
                    description "TCP port of the scrape listener.";
                }
                leaf http-path {
                    type string;
                    default "/metrics";
                    srl-ext:show-importance high;
                    description "HTTP path Prometheus scrapes.";
                }
                leaf oper-state {
                    type srl-comm:oper-state;
                    config false;
                    description "Operational state of the scrape listener.";
                }
                leaf scrapes-count {
                    config false;
                    type srl-comm:zero-based-counter64;
                    description "Number of scrapes received.";
                }
            }
            leaf network-instance {
                type leafref {
                    path "/srl-netinst:network-instance/srl-netinst:name";
                }
                srl-ext:show-importance high;
                default "mgmt";
                description
                    "Network-instance used by the scrape listener and by remote write.";
            }
            leaf tls-profile {
                type leafref {
                    path "/srl-system:system/srl-tls:tls/srl-tls:profile/srl-tls:name";
                }
                srl-ext:show-importance high;
                description
                  "TLS profile for the scrape listener and for remote write when the URL is https.

                   The profile certificate and key are presented by the listener and by the
                   remote-write client. The profile trust anchor verifies the remote-write server.";
            }
            leaf admin-state {
                type srl-comm:admin-state;
                default "disable";
                must ". = 'disable' or /srl-system:system/srl-ndk:ndk-server/srl-ndk:admin-state = 'enable'" {
                    error-message
                      "The NDK server must be enabled before enabling the Prometheus exporter";
                }
                must ". = 'disable' or /srl-system:system/srl-grpc:grpc-server[srl-grpc:name = current()/../grpc-server]/srl-grpc:admin-state = 'enable'" {
                    error-message
                      "The grpc-server referenced by grpc-server must exist and be enabled";
                }
                must ". = 'disable' or /srl-system:system/srl-grpc:grpc-server[srl-grpc:name = current()/../grpc-server]/srl-grpc:unix-socket/srl-grpc:admin-state = 'enable'" {
                    error-message
                      "The grpc-server referenced by grpc-server must have unix-socket admin-state enable";
                }
                must ". = 'disable' or not(/srl-system:system/srl-grpc:grpc-server[srl-grpc:name = current()/../grpc-server]/srl-grpc:unix-socket/srl-grpc:socket-filename)" {
                    error-message
                      "The grpc-server referenced by grpc-server must not set unix-socket socket-filename";
                }
                srl-ext:show-importance high;
                description "Administrative state of the exporter";
            }
            leaf grpc-server {
                type leafref {
                    path "/srl-system:system/srl-grpc:grpc-server/srl-grpc:name";
                    require-instance false;
                }
                default "prometheus-exporter";
                srl-ext:show-importance high;
                description
                  "gRPC server whose unix socket the exporter uses for gNMI.

                   The exporter connects to
                   /opt/srlinux/var/run/sr_grpc_server_<grpc-server>. The server
                   must be enabled, enable its unix-socket, and leave
                   socket-filename unset. It must also include the gnmi
                   service; that is not checked at commit.";
            }
            leaf debug {
                type srl-comm:admin-state;
                default "disable";
                description
                  "Enable debug logging in the exporter process.

                   The default is disable. When enabled, configuration and
                   network-instance notifications are logged. The change
                   applies on commit without restarting the process.";
            }
            leaf oper-state {
                type srl-comm:oper-state;
                config false;
                srl-ext:show-importance high;
                description "Operational state of the exporter application.";
            }
            list metric {
                description "Predefined metrics to be exposed on the prometheus exporter server";
                key "name";
                leaf name {
                    type enumeration {
                        enum aaa;
                        enum acl;
                        enum bgp;
                        enum interfaces;
                        enum isis;
                        enum lldp;
                        enum mpls;
                        enum network-instance-bridge-table;
                        enum network-instance-icmp;
                        enum network-instance-icmp6;
                        enum platform;
                        enum route-table-ipv4-unicast;
                        enum route-table-ipv6-unicast;  
                        enum subinterfaces;
                        enum tcp;              
                        enum udp;
                    }
                }
                leaf admin-state {
                    type srl-comm:admin-state;
                    default "disable";
                    srl-ext:show-importance high;
                    description "Specifies whether this metric is collected on prometheus client scrapes or not";
                }
                leaf-list paths {
                    config false;
                    max-elements 16;
                    type string;
                    srl-ext:show-importance high;
                    description "gNMI xpaths used to subscribe for updates exposed by this metric";
                }
                leaf help-text {
                    type string;
                    default "SRLinux generated metric";
                    description "Prometheus metric help text";
                }
            } // list metric
            list custom-metric {
                description "User defined prometheus metric";
                key "name";
                leaf name {
                    type string;
                    description "Custom metric name";
                }
                leaf-list paths {
                    max-elements 16;
                    type string;
                    description "gNMI xpaths used to subscribe for updates exposed by this custom metric";
                }
                leaf admin-state {
                    type srl-comm:admin-state;
                    default "disable";
                    srl-ext:show-importance high;
                    description "Specifies whether this metric is collected on prometheus client scrapes or not";
                }
                leaf help-text {
                    type string;
                    default "SRLinux generated metric";
                    description "Prometheus metric help text";
                }
            } // list custom-metric
            container remote-write {
                description
                  "Push samples to a Prometheus remote-write endpoint.

                   The exporter opens a gNMI STREAM subscription in SAMPLE mode.
                   sample-interval is the interval leaf. Each sample is posted
                   to url. The CPM filter must accept TCP replies whose source
                   port is the remote-write server port.";
                leaf url {
                    type string;
                    description
                      "Remote-write endpoint, for example http://192.0.2.1:9090/api/v1/write.";
                }
                leaf interval {
                    type string;
                    default "15s";
                    description
                      "gNMI sample interval. Samples are written on this interval.";
                }
                leaf timeout {
                    type string;
                    default "30s";
                    description "HTTP timeout for one remote-write POST.";
                }
                leaf username {
                    type string;
                    description "Basic-auth username. Leave unset for no authentication.";
                }
                leaf password {
                    type string;
                    description "Basic-auth password.";
                }
                leaf admin-state {
                    type srl-comm:admin-state;
                    default "disable";
                    must ". = 'disable' or ../url" {
                        error-message
                          "remote-write url is required when remote-write is enabled";
                    }
                    description "Administrative state of remote write.";
                }
                leaf oper-state {
                    type srl-comm:oper-state;
                    config false;
                    description "Operational state of remote write.";
                }
                leaf writes-count {
                    config false;
                    type srl-comm:zero-based-counter64;
                    description "Number of successful remote-write posts.";
                }
                leaf last-error {
                    config false;
                    type string;
                    description "Last remote-write error. Empty after a successful post.";
                }
            }
            container registration {
                leaf address {
                    type string;
                    srl-ext:show-importance high;
                    description "Consul server address";
                }
                leaf username {
                    type string;
                    srl-ext:show-importance high;
                    description "Consul server username";
                }
                leaf password {
                    type string;
                    srl-ext:show-importance high;
                    description "Consul server username";
                }
                leaf token {
                    type string;
                    srl-ext:show-importance high;
                    description "Consul server access token";
                }
                leaf ttl {
                    type string;
                    default "5s";
                    srl-ext:show-importance high;
                    description "Registration TTL";
                }
                leaf http-check {
                    type boolean;
                    default false;
                    description "Enable Consul HTTP Check";
                }
                leaf-list tags {
                    type string;
                    description "List of tags to be added to the service registration";
                }
                leaf admin-state {
                    type srl-comm:admin-state;
                    default "disable";
                    srl-ext:show-importance high;
                    description "Administrative state of the registration";
                }
                leaf oper-state {
                    type srl-comm:oper-state;
                    config false;
                    srl-ext:show-importance high;
                    description "Operational state of the registration";
                }
            } // container registration
        } // container prometheus-exporter
    } // grouping prometheus-exporter-top

    augment "/srl-system:system" {
        uses prometheus-exporter-top;
    }
}
